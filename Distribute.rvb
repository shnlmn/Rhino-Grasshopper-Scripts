Option Explicit
'Script written by Pascal

'Script version Saturday, September 03, 2011 

Rhino.AddStartupScript Rhino.LastLoadedScriptFile()
Rhino.AddAlias "Distribute", "_NoEcho _-Runscript (Distribute)"

Private OldDDir, OldGapStyle, oldGap, OldCSpace

If IsEmpty(OldDDir) Then
	OldDDir = "X"
End If

If IsEmpty(OldGapStyle) Then
	OldGapStyle = "Centers"
End If

If IsEmpty(OldCSpace) Then
	OldCSpace = 1
End If

If IsEmpty(OldGap) Then
	OldGap = 1
End If

'Call Distribute()

Sub Distribute()
	
	Dim i
	Dim aObj: aObj = Rhino.GetObjects("Select objects to distribute.",,, True)
	If Not IsArray(aObj) Then Exit Sub
	
	Dim aGrps: aGrps = SortObjectsToGroups(aObj)
	'aGrps(2)
	'0 = all objects in multiple groups
	'1 = all objects in one group, or no grps
	'2 = some grouped and some ungrouped
	
	Dim allGrps 
	If aGrps(2) = 1 Then 
		AllGrps = aGrps(1)	
	ElseIf aGrps(2) = 2 Then
		allGrps = rhino.JoinArrays(aGrps(0), aGrps(1))
	ElseIf aGrps(2) = 0 Then
		AllGrps = aGrps(0)
	End If
	
	If  Ubound(allGrps) < 1 Then
		msgBox "At least 2 objects must be selected."
		Exit Sub
	End If	

	Dim Bound: Bound = UBound(allGrps)
	
	'get thew users choice of the distribution direction
	Dim aDir: aDir = Array("X", "Y", "User")
	Dim sDir: sDir = Rhino.GetString("Direction", OldDDir, aDir)
	If IsNull(sDir) Then Exit Sub
	
	'check that the result is valid
	Dim intDir: intDir = WhereInArray(sDir, aDir, 1)
	
	If intDir = -1 Then Exit Sub
	
	'set the sticky option
	If intDir <> 2 Then
		OldDDir = UCase(sDir)
	Else
		oldDDir = "User"
	End If
	
	Dim TempPlane: TempPlane = Rhino.ViewCPlane()
	Dim Plane
	
	'Get a plane from the direction and the current cplane
	
	'if the direction is the cplane X, use the view cplane
	If intDir = 0 Then
		Plane = TempPlane
		'if the direction is Y rotate the plane on Z, 90 degrees
	ElseIf intDir = 1 Then 
		Plane = Rhino.RotatePlane(TempPlane, 90, TempPlane(3))
	Else
		'get a plane from the user defined direction
		Plane = GetPlaneFromDirection()
		If Not IsArray(Plane) Then Exit Sub
		'DrawPlaneFrame plane, 10 'TEST
	End If
	
	'get the gap style from the user- 
	'either between centers or by equal
	'spacing between bounding box edges
	Dim aStyle: aStyle = Array("Centers", "Gap", "SetCenters", "SetGap")
	
	Dim sStyle: sStyle = Rhino.GetString("Set spacing style.", OldGapStyle, aStyle)
	If IsNull(sStyle) Then Exit Sub
	
	Dim intStyle: intStyle = WhereInArray(sStyle, aStyle, 1)
	
	If intStyle = -1 Then Exit Sub
	
	OldGapStyle = aStyle(intStyle)

	'Order the selected objects in the direction to distribute
	' as well as an ordered set of BBox centers
	Dim Orderly: Orderly = OrderGroups(AllGrps, Plane)
	
	If Not isArray(Orderly) Or UBound(allGrps) < 2 Then
		
		If intStyle < 2 Then
			msgbox "Unable to determine spacing." & vbNewLine & " At least 3 objects must be selected for automatic spacing."
			If isArray(Orderly(1)) Then
				For Each sGrp In aGrps(1)
					Rhino.DeleteGroup sGrp
				Next
			End If
			Exit Sub
	
		End If
		
	End If
	
	Dim aOrderedGrp
	
	If isArray(Orderly) Then
		Dim j, k
		j = Orderly(0)
		k = Orderly(1)
		If IsArray(j) Then
			If isArray(k) Then
				aOrderedGrp = Rhino.JoinArrays(J, K)
			Else
				aOrderedGrp = j
			End If
		Else
			If isArr(k) Then 
				aOrderedGrp = k
			Else
				Exit Sub
			End If
		End If
		
	End If
	
	'Dim aCen: aCen = Orderly(1)
	Dim testLine: testLine = Array(Plane(0), Rhino.PointAdd(Plane(0), Plane(1)))
	Dim Space, span, CSpace, aCen
	
	If intStyle = 0 Then 'Centers
	 
		aCen = Orderly(1)
		'calculate the spacing between BB centers  fomr
		'the ordered array of Bbox centers.
		Space = qDistance(aCen(0), aCen(Bound)) / Bound
		
	ElseIf intStyle = 2 Then 'ExplicitCenters
		aCen = Orderly(1)
		Space = rhino.GetReal("Set center spacing.", oldCSpace)
		If isNull(Space) Then Exit Sub
		oldCSpace = Space

	ElseIf intStyle = 3 Then 'ExplicitGap
		Space = rhino.GetReal("Set gap size.", oldgap)
		If isNull(space) Then Exit Sub
		oldGap = Space
		
	Else 'gap
		'Calculate the desired space between bounding box edges
		Dim temp
		Dim ttl_length: ttl_length = 0
		'add up the total length of the middle objects in the distribute direction
		For i = 1 To Bound - 1
			temp = Rhino.BoundingBox(Rhino.ObjectsByGroup(aOrderedGrp(i)), Plane)
			ttl_length = ttl_length + qDistance(temp(0), temp(1))
		Next
		
		'find the max extent of the first object and the min extent of the last object
		'project the points to the plane X axis
		Dim Pt1:	Pt1 = Rhino.LineClosestPoint(TestLine, Rhino.BoundingBox(Rhino.ObjectsByGroup(aOrderedGrp(0)), Plane)(1))
		Dim Pt2:	pt2 = Rhino.LineClosestPOint(TestLine, Rhino.BoundingBox(Rhino.ObjectsByGroup(aOrderedGrp(Bound)), Plane)(0))
		
		'calculate the span
		span = qDistance(Pt1, Pt2)
		Space = (Span - ttl_length) / bound
		
	End If
		
	Dim sObj, base, min
	'	DrawPlaneFrame Plane, 5
	
	Rhino.EnableRedraw False

	'Move the objects
	If intStyle = 0 Then Bound = Bound - 1
	
	If intStyle = 0 Or intStyle = 2 Then 'Centers
		For i = 1 To bound 
		
			Rhino.MoveObjects Rhino.ObjectsByGroup(aOrderedGrp(i)), aCen(i), Rhino.PointAdd(aCen(0), Rhino.VectorScale((Plane(1)), i * Space))
		Next
	Else 'gap
		
		'make a vector the length of the desired spacing
		Dim vec: vec = Rhino.VectorScale(Plane(1), Space)
		
		'Move each middle object from its current Min point to the previous objects
		'max point plus the spacing vector
		
		If intStyle = 1 Then bound = bound - 1
		Dim sGrp
		For i = 1 To bound 
		
			sGrp = aOrderedGrp(i)'current object
			
			'min point, projected to the direction line
			min = Rhino.LineClosestPoint(TestLine, Rhino.BoundingBox(Rhino.ObjectsByGroup(aOrderedGrp(i)), Plane)(0))
			
			'Previous object's max point, projected to the direction line
			temp = Rhino.BoundingBox(Rhino.ObjectsByGroup(aOrderedGrp(i - 1)), Plane)'previous object bb
			Base = Rhino.LineClosestPoint(TestLine, Temp(1))
			Rhino.MoveObjects Rhino.ObjectsByGroup(sGrp), Min, Rhino.PointAdd(Base, vec)
		
		Next
		
	End If
	
	If isArray(Orderly(1)) Then
		For Each sGrp In aGrps(1)
			Rhino.DeleteGroup sGrp
		Next
	End If
	
	Rhino.EnableRedraw True
	
End Sub

Function OrderGroups(aGrps, Plane)
	
	Dim i, temp, tempBox
	Dim Bound: Bound = UBound(aGrps)
	Dim testLine: testLine = array(Plane(0), Rhino.PointAdd(plane(0), Plane(1)))
	Dim  aBB, aCen
	
	Dim aObj, tempObj
	aObj = Rhino.ObjectsByGroup(aGrps(0))
	For i = 1 To Ubound(agrps)
		tempObj = Rhino.ObjectsByGroup(aGrps(i))
		If isArray(tempObj) Then aObj = Rhino.JoinArrays(aobj, tempObj)
	Next
	
	aBB = Rhino.BoundingBox(aObj, Plane)
	Plane(0) = AveragePoints(Array(aBB(0), aBB(6)))

	ReDim aCen(Bound)
	
	Dim XForm: Xform = Rhino.XformRotation(Plane, Rhino.WorldXYPlane())
	Dim revXForm: revXform = Rhino.XformRotation(Rhino.WorldXYPlane(), Plane)
	
	Dim dblSum: dblSum = 0
	
	For i = 0 To Bound
		
		tempBox = Rhino.BoundingBox(Rhino.ObjectsByGroup(aGrps(i)), Plane)
		dblSum = dblSum + qDistance(tempBox(0), tempBox(1))
		temp = AveragePoints(Array(tempBox(0), tempBox(6)))
		aCen(i) = Rhino.PointTransform(Rhino.LineClosestPoint(TestLine, temp), xform)
		
	Next
	

	Dim aOrderedCen: aOrderedCen = Rhino.SortPoints(aCen)
	Dim TestArr: TestArr = Rhino.CullDuplicatePoints(aOrderedCen)

	If Ubound(testArr) < 1 Then
		
		OrderGroups = Array(aGrps, aOrderedCen)
		'msgbox "Unable to determine spacing."
		Exit Function
	End If
	
	Dim j, n, OrderedGrp

	ReDim OrderedGrp(Bound)
	n = 0
	
	For i = 0 To UBound(TestArr)
		For j = 0 To Bound
			If Rhino.PointCompare(TestArr(i), aCen(j)) Then
				OrderedGrp(n) = aGrps(j)
				n = n + 1
			End If
		Next
	Next
	
	For i = 0 To Bound
		aOrderedCen(i) = Rhino.PointTransform(aOrderedCen(i), revXform)
	Next
	

	OrderGroups = Array(OrderedGrp, aOrderedCen)
	
End Function

Function QDistance(aPtA, aPtB)
	QDistance = Sqr((aPtA(0) - aPtB(0)) ^ 2 + (aPtA(1) - aPtB(1)) ^ 2 + (aPtA(2) - aPtB(2)) ^ 2)
End Function

Function WhereInArray(item, arr, intCase)
	'Finds the locaton of a string in an array of strings
	'if the result is -1 then the item does not
	'appear in tha array

	Dim sItem, n, i
	n = False
	WhereInArray = -1

		
	For i = 0 To UBound(arr)
			
		If intCase = 0 Then
			If arr(i) = Item Then
				
				WhereInArray = i
				n = True
				Exit For
		
				
			End If
			
		Else 
			
			If LCase(arr(i)) = LCase(Item) Then
				
				WhereInArray = i
				n = True
				Exit For
	
			End If
			
		End If
			
	Next
	

	If n = False Then WhereInArray = -1
	
End Function

Function AveragePoints(aPts)
	'Finds the average coordinates of an array
	'of points.

	Dim X, Y, Z
	Dim i
	
	X = 0
	Y = 0
	Z = 0

	For i=0 To UBound(aPts)
			
		'add all the X values
		X = X + aPts(i)(0)
	
		'add all th Y values
		Y = Y + aPts(i)(1)			
	
		'add all the Z values
		Z = Z + apts(i)(2)
	Next
	
	'Divide by the number of points to
	'get the average  for each
	'create the output array from the 3 averages
	AveragePoints = Array(X / (UBound(aPts) + 1), Y / (UBound(aPts) + 1), Z / (UBound(aPts) + 1))

End Function

Function GetPlaneFromDirection()
	
	Dim aPts: aPts = Rhino.GetPoints(True,, "First direction point.", "Second dimrection point.", 2)
	If Not IsArray(aPts) Then Exit Function
	
	Dim vecDir: vecDir = Rhino.VectorCreate(apts(1), aPts(0))
	Dim tempPlane: tempPlane = Rhino.PlaneFromNormal(aPts(0), vecdir)
	'DrawPlaneFrame tempPlane, 10
	GetPlaneFromDirection = Rhino.PlaneFromFrame(aPts(0), Rhino.VectorUnitize(vecDir), Rhino.VectorUnitize(tempPLane(1)))

End Function

Function SortObjectsToGroups(aObj)
	
	Dim AllOne: AllOne = -1
	'0 = all objects in multiple groups
	'1 = all objects in one group, or no grps
	'2 = some grouped and some ungrouped
	
	
	Dim temp: temp = Rhino.GroupNames()
	Dim X, sObj, n,i
	i = 0
	n = 0
	Dim aGrps(), atempGrps()
	
	If Not isArray(temp) Then 'No existing groups
		
		For Each sObj In aObj
			X = Rhino.AddGroup
			ReDim Preserve aGrps(n)
			ReDim Preserve atempGrps(n)
			atempGrps(n) = X
			aGrps(n) = X
			n = n + 1
			Rhino.AddObjectToGroup sObj, X
			allOne = 1 'no preexisting groups
		Next
		
	Else 'some existing groups
	
		Dim objGrps, Bound
		For Each sObj In aObj
			
			objGrps = Rhino.ObjectGroups(sObj)
			If isArray(objGrps) Then
				bound = UBound(objGrps)
				ReDim Preserve aGrps(n)
				aGrps(n) = objGrps(Bound)
				n = n + 1
			Else
				X = Rhino.AddGroup()
				'ReDim Preserve aGrps(n)
				ReDim Preserve atempGrps(i)
				atempGrps(i) = X
				'	aGrps(n) = X
				'	n = n + 1
				i = i + 1
				Rhino.AddObjectToGroup sObj, X
				
			End If
	
		Next
		
	End If
	
	Dim aNewGrps
	
	If n > 0 Then 'Some objects in pre-existing groups
		
		AllOne = 0 'all objects in multiple groups
		If i > 0 Then allOne = 2 'some ungrouped objects	
		
		aNewGrps = Rhino.CullDuplicateStrings(aGrps)
	
		If Ubound(aNewGrps) = 0 Then
			If i = 0 Then
				If i = 0 Then AllOne = 1 ' all grouped objects in one group
				
				ReDim atempGrps(Ubound(aObj))

				For i = 0 To Ubound(aObj)
					X = Rhino.AddGroup()
					Rhino.AddObjectToGroup aobj(i), X
					atempGrps(i) = X
				Next
			End If
		End If
		
	Else
		AllOne = 1
	End If
	
	
	
	SortObjectsToGroups = array(aNewGrps, aTempGrps, AllOne)
	
End Function

Function CullEmptyGroups(aGroups)
	
	Dim result(), n, sGrp
	n = 0
	For Each sGrp In aGrps
		If Not Rhino.IsGroupEmpty(Sgrp) Then
			ReDim Preserve result(n)
			result(n) = sGrp
			n = n + 1
		End If
	Next
	CullEmptyGroups = result
	
End Function


Function IsUpperBound(ByRef arr)

	IsUpperBound = False

	If IsArray(arr) Then

		On Error Resume Next

		UBound arr

		If Err.Number = 0 Then IsUpperBound = True

	End If

End Function

Sub DrawPlaneFrame (aPlane, dblScale)
	'For testing
	Rhino.EnableRedraw(False)
	
	Dim pt0: Pt0 = aPlane(0)
	Dim aLines(5)
	
	Dim vec1: vec1 = Rhino.VectorScale(aPlane(1), dblScale)
	Dim pt1: Pt1 = Rhino.PointAdd(Pt0, vec1)
	Dim Pt4: Pt4 = Rhino.PointAdd(Pt0, Rhino.VectorReverse(Vec1))

	Dim vec2: vec2 = Rhino.VectorScale(aPlane(2), dblScale)
	Dim pt2: Pt2 = Rhino.PointAdd(Pt0, Vec2)	
	Dim Pt5: Pt5 = Rhino.PointAdd(Pt0, Rhino.VectorReverse(Vec2))
	Dim vec3: vec3 = Rhino.VectorScale(aPlane(3), dblScale)
	Dim pt3: Pt3 = Rhino.PointAdd(Pt0, Vec3)	
	Dim Pt6: Pt6 = Rhino.PointAdd(Pt0, Rhino.VectorReverse(Vec3))
	
	aLines(0) = Rhino.AddLine(Pt0, Pt1)
	aLines(1) = Rhino.AddLine(Pt0, pt2)
	aLines(2) = Rhino.AddLine(Pt0, Pt3)
	aLines(3) = Rhino.AddLine(Pt0, Pt4)
	aLines(4) = Rhino.AddLine(Pt0, Pt5)
	aLines(5) = Rhino.AddLine(Pt0, Pt6)
	
	Rhino.ObjectColor Array(alines(0), alines(3)), vbRed
	Rhino.ObjectColor Array(alines(1), alines(4)), vbGreen
	Rhino.ObjectColor Array(alines(2), alines(5)), vbBlue
	
	Dim i
	For i = 0 To 2
		Rhino.CurveArrows aLines(i), 2
	Next
			
	Dim sgrp: sGrp = Rhino.AddGroup
	
	Rhino.AddObjectsToGroup aLines, sGrp
	Rhino.EnableRedraw(True)
	
End Sub
